BadConfigSelective DEFINITIONS AUTOMATIC TAGS ::= BEGIN
              Seq ::= SEQUENCE {
                    a INTEGER,
                    b SEQUENCE OF INTEGER,
                    c BOOLEAN,
                    cc CHOICE {
                       ca INTEGER,
                       cb BOOLEAN
                    }
              }
            END
