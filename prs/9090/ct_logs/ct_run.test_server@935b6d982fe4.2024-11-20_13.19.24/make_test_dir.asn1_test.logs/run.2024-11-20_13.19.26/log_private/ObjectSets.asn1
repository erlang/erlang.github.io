ObjectSets DEFINITIONS AUTOMATIC TAGS ::= BEGIN
TEST-UNIQ ::= CLASS { &id INTEGER UNIQUE,  &test INTEGER }
UniqSet TEST-UNIQ ::= { { &id 1, &test 1 } | {&id 1, &test 2} }
DOUBLE-UNIQ ::= CLASS { &id1 INTEGER UNIQUE,           &id INTEGER UNIQUE }
DoubleSet DOUBLE-UNIQ ::= { {&id1 1, &id2 2} }
END
