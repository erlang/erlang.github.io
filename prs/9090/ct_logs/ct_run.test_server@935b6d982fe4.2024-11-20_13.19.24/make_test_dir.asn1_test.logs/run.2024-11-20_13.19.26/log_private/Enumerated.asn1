Enumerated DEFINITIONS AUTOMATIC TAGS ::= BEGIN
  Enum ::= ENUMERATED { a, b, c }
  e Enum ::= d
  EnumExt ::= ENUMERATED { x, ..., y }
  ext EnumExt ::= z
  S1 ::= SEQUENCE {
    ge1 Enum DEFAULT a,
    ge2 EnumExt DEFAULT x,
    ge3 EnumExt DEFAULT y,
    e Enum DEFAULT aa
  }
  S2 ::= SEQUENCE {
    e2 EnumExt DEFAULT xyz
  }
  BadEnum1 ::= ENUMERATED {a, b, c, b }
  BadEnum2 ::= ENUMERATED {a(1), b(2), b(3) }
  BadEnum3 ::= ENUMERATED {a(1), b(1) }
  BadEnum4 ::= ENUMERATED {a, b, ..., c(0) }
  BadEnum5 ::= ENUMERATED {a, b, ..., c(10), d(5) }
END
