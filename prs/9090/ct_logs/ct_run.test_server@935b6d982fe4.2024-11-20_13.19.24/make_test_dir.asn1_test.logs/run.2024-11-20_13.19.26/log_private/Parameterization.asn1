Parameterization DEFINITIONS AUTOMATIC TAGS ::= BEGIN
  NotUppercase{lowercase} ::= INTEGER (lowercase)
  P{T1,T2} ::= SEQUENCE { a T1, b T2 }
  S ::= P{OCTET STRING}
  Seq ::= SEQUENCE { a INTEGER }
  Sbad ::= Seq{INTEGER}
END
