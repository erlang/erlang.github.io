REL-OIDS DEFINITIONS AUTOMATIC TAGS ::= BEGIN
legal-oid OBJECT IDENTIFIER ::= {1 2}
legal-roid RELATIVE-OID ::= {1 2}
CONTAINER ::= CLASS { &oid OBJECT IDENTIFIER OPTIONAL,
                      &int INTEGER OPTIONAL,
                      &seq SEQUENCE { a INTEGER } OPTIONAL
}
object-1 CONTAINER ::= { &oid {1 2 3},
                         &int 42,
                         &seq {a 42}
                       }
wrong-type-rel-oid-1 RELATIVE-OID ::= legal-oid
wrong-type-rel-oid-2 RELATIVE-OID ::= object-1.&oid
wrong-type-rel-oid-3 RELATIVE-OID ::= object-1.&int
wrong-type-rel-oid-4 RELATIVE-OID ::= object-1.&seq
wrong-type-rel-oid-5 RELATIVE-OID ::= object-1.&undef
oid-bad-first OBJECT IDENTIFIER ::= {legal-roid 3}
roid-bad-first RELATIVE-OID ::= {legal-oid 3}
END
