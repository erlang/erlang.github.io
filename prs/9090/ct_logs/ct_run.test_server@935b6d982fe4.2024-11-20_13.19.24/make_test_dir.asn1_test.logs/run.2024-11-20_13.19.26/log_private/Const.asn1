Const DEFINITIONS AUTOMATIC TAGS ::= BEGIN
  Seq1 ::= SEQUENCE {a INTEGER, b BIT STRING, a BOOLEAN}
  Ch   ::= CHOICE {a INTEGER, b BIT STRING, a BOOLEAN}
  Seq2 ::= SEQUENCE {COMPONENTS OF Ch}
  CL   ::= CLASS { &id INTEGER UNIQUE, &Type }
  Seq3 ::= SEQUENCE { id CL.&id, d CL.&foo }
  Seq4 ::= SEQUENCE { a INTEGER, z INTEGER OPTIONAL, b Set1 }
  Set1 ::= SET { c BOOLEAN, d INTEGER }
  s1 Seq4 ::= {a 42, b {c TRUE, zz 4711}}
  s2 Seq4 ::= {a 42, b {c TRUE, d FALSE}}
  s3 Seq4 ::= {a 42, b {c TRUE}}
  s4 Seq4 ::= {a 42, b {c TRUE, d 4711}, zz 4712}
  s5 Seq4 ::= {a 42}
  s6 Seq4 ::= {a 42, zz 4712, b {c TRUE, d 4711}}
END
