Already DEFINITIONS ::= BEGIN
  I ::= INTEGER
  i I ::= 42
  I ::= OCTET STRING
  I ::= CLASS { &Type }
  MYCLASS ::= CLASS { &Type }
  i MYCLASS ::= { &Type INTEGER }
  o MYCLASS ::= { &Type INTEGER }
  I MYCLASS ::= { o }
  I{T} ::= SEQUENCE OF T
  I{INTEGER:x} INTEGER ::= { 1 | 2 | x }
  i{T} MYCLASS ::= { &Type T }
END
