BadConfigExclusive DEFINITIONS AUTOMATIC TAGS ::= BEGIN
              Seq ::= SEQUENCE {
                    a INTEGER,
                    b SEQUENCE OF INTEGER,
                    c BOOLEAN
              }
            END
