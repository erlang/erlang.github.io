ObjectFieldExtraction DEFINITIONS AUTOMATIC TAGS ::= BEGIN
  DataObjSet DATA-CLASS ::= {
    holder-object-1.&int,
    ...
  }
  DataObjSetNoExt DATA-CLASS ::= {
    holder-object-1.&int
  }
  holder-object-1 HOLDER-CLASS ::= {
    &int 42
  }
  HOLDER-CLASS ::= CLASS {
    &int INTEGER
  }
  DATA-CLASS ::= CLASS {
    &id INTEGER
  }
END
