TableConstraints DEFINITIONS AUTOMATIC TAGS ::= BEGIN
  Seq-1 ::= SEQUENCE {
    contentType CONTENTS.&id,
    content CONTENTS.&Type({Contents}{@contentType})
  }
  Seq-2 ::= SEQUENCE {
    contentType INTEGER,
    content CONTENTS.&Type({Contents}{@contentType})
  }
  Int ::= INTEGER ({1})
  Seq-3 ::= SEQUENCE {
    contentType CONTENTS.&id({1})
  }
Contents CONTENTS ::= {
  {OCTET STRING IDENTIFIED BY {2 1 1}}
}
CONTENTS ::= TYPE-IDENTIFIER
END
