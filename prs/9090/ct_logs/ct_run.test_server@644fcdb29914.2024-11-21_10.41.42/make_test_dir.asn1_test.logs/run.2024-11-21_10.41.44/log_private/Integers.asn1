Integers DEFINITIONS AUTOMATIC TAGS ::= BEGIN
  Int1 ::= INTEGER {a(1), a(1)}
  Int2 ::= INTEGER {a(1), b(2), a(3)}
  Int3 ::= INTEGER {x(1), y(1)}
  i0 INTEGER ::= 1
  Int4 ::= INTEGER {x(i0), y(undef) }
END
