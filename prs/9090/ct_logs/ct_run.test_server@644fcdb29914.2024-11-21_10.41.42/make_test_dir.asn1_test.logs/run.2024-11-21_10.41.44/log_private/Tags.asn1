Tags DEFINITIONS AUTOMATIC TAGS ::= BEGIN
SeqOpt1 ::= SEQUENCE
{
bool1  BOOLEAN OPTIONAL,
int1  INTEGER,
seq1  SeqIn OPTIONAL
}
SeqOpt1Imp ::= SEQUENCE 
{
bool1 [1] BOOLEAN OPTIONAL,
int1  INTEGER,
seq1  [2] SeqIn OPTIONAL,
seq2  [2] SeqIn OPTIONAL,
...,
int2  [3] SeqIn,
int3  [3] SeqIn
}
SeqIn ::= SEQUENCE 
{
boolIn  BOOLEAN,
intIn  INTEGER
}

Set1 ::= SET {
 os [0] OCTET STRING,
 bool [0] BOOLEAN
}
Seq1 ::= SEQUENCE {
a [0] IMPLICIT Choice OPTIONAL
}
Seq2 ::= SEQUENCE {
a [0] IMPLICIT ANY OPTIONAL
}
Choice ::=
CHOICE {
a [0] BOOLEAN,
b [1] INTEGER
}
END
