OIDS DEFINITIONS AUTOMATIC TAGS ::= BEGIN
CONTAINER ::= CLASS { &id OBJECT IDENTIFIER UNIQUE,
                      &int INTEGER OPTIONAL,
                      &seq SEQUENCE { a INTEGER } OPTIONAL
}
-- This is line 6.
object-1 CONTAINER ::= { &id {1 2 3}, &int 42 }
object-2 CONTAINER ::= { &id {1 999}, &int 0 }
object-3 CONTAINER ::= { &id {1 2}, &seq { a 42 } }
oid-1 OBJECT IDENTIFIER ::= object-1.&int
oid-2 OBJECT IDENTIFIER ::= object-2.&id
oid-3 OBJECT IDENTIFIER ::= object-3.&seq
-- This is line 13.
oid-5 OBJECT IDENTIFIER ::= { a 42, b 19 }
oid-6 OBJECT IDENTIFIER ::= int
int INTEGER ::= 42
oid-7 OBJECT IDENTIFIER ::= seq
seq SEQUENCE { x INTEGER } ::= { x 11 }
oid-8 OBJECT IDENTIFIER ::= os
os OCTET STRING ::= '1234'H
oid-9 OBJECT IDENTIFIER ::= { 1 os }
oid-10 OBJECT IDENTIFIER ::= { 1 invalid }
-- This is line 23.
oid-11 OBJECT IDENTIFIER ::= { 0 legal-oid }
legal-oid OBJECT IDENTIFIER ::= {1 2 3}
bad-root-1 OBJECT IDENTIFIER ::= {99}
bad-root-2 OBJECT IDENTIFIER ::= {0 42}
oid-object-ref-1 OBJECT IDENTIFIER ::= object-1
oid-object-ref-2 OBJECT IDENTIFIER ::= { object-1 19 } 
oid-int OBJECT IDENTIFIER ::= 42
oid-sequence OBJECT IDENTIFIER ::= {a 42, b 35}
END
